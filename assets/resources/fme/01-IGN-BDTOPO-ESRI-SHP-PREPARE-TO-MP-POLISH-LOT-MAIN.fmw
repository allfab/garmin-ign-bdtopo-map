FME workspace 01-IGN-BDTOPO-ESRI-SHP-PREPARE-TO-MP-POLISH-LOT-MAIN.fmw

Parameters:
- VERSION = v2025.06   # Version de la BDTOPO ?
- TERRITOIRE = FRANCE-SUD   # Sélectionner un territoire ?
- INPUT_DATA_TERRITORY = E:\GARMIN\GARMIN-IGN-BDTOPO-MAP\03-DATA-INPUT\01-IGN-BDTOPO\01-SHP\$(TERRITOIRE)\$(VERSION)   # Dossier contenant les données IGN en entrée
- OUTPUT_DATA_TERRITORY = E:\GARMIN\GARMIN-IGN-BDTOPO-MAP\04-DATA-OUTPUT\$(TERRITOIRE)\$(VERSION)\01-BDTOPO   # Dossier de sortie des données SHAPE
- SourceDataset_CSV2 = E:\GARMIN\GARMIN-IGN-BDTOPO-MAP\03-DATA-INPUT\05-INSEE\region_2022.csv   # Fichier(s) source CSV (Comma Separated Value)
- SourceDataset_SHAPEFILE_47 = $(INPUT_DATA_TERRITORY)\**\COMMUNE.shp   # Shapefile(s) Esri source
- SourceDataset_SHAPEFILE_33 = $(INPUT_DATA_TERRITORY)\**\TRONCON_HYDROGRAPHIQUE.shp   # Shapefile(s) Esri source
- SourceDataset_SHAPEFILE_48 = $(INPUT_DATA_TERRITORY)\**\SURFACE_HYDROGRAPHIQUE.shp   # Shapefile(s) Esri source
- SourceDataset_SHAPEFILE_41 = $(INPUT_DATA_TERRITORY)\**\DETAIL_HYDROGRAPHIQUE.shp   # Shapefile(s) Esri source 
- SourceDataset_SHAPEFILE_37 = $(INPUT_DATA_TERRITORY)\**\TOPONYMIE_HYDROGRAPHIE.shp   # Shapefile(s) Esri source 
- SourceDataset_SHAPEFILE_49 = $(INPUT_DATA_TERRITORY)\**\TOPONYMIE_LIEUX_NOMMES.shp   # Shapefile(s) Esri source 
- SourceDataset_SHAPEFILE_34 = $(INPUT_DATA_TERRITORY)\**\TOPONYMIE_SERVICES_ET_ACTIVITES.shp   # Shapefile(s) Esri source 
- SourceDataset_SHAPEFILE_36 = $(INPUT_DATA_TERRITORY)\**\ZONE_D_ACTIVITE_OU_D_INTERET.shp   # Shapefile(s) Esri source 
- SourceDataset_SHAPEFILE_38 = $(INPUT_DATA_TERRITORY)\**\LIGNE_ELECTRIQUE.shp   # Shapefile(s) Esri source 
- SourceDataset_SHAPEFILE_40 = $(INPUT_DATA_TERRITORY)\**\FORET_PUBLIQUE.shp   # Shapefile(s) Esri source 
- SourceDataset_SHAPEFILE = $(INPUT_DATA_TERRITORY)\**\ZONE_D_HABITATION.shp   # Shapefile(s) Esri source 

Readers:
- CSV2_1: CSV2 from $(SourceDataset_CSV2)
- SHAPEFILE_25: SHAPEFILE from $(SourceDataset_SHAPEFILE_47) in EPSG:2154
- SHAPEFILE_1: SHAPEFILE from $(SourceDataset_SHAPEFILE) in EPSG:2154
- SHAPEFILE_2: SHAPEFILE from $(SourceDataset_SHAPEFILE_33) in EPSG:2154
- SHAPEFILE_3: SHAPEFILE from $(SourceDataset_SHAPEFILE_48) in EPSG:2154
- SHAPEFILE_4: SHAPEFILE from $(SourceDataset_SHAPEFILE_41) in EPSG:2154
- SHAPEFILE_5: SHAPEFILE from $(SourceDataset_SHAPEFILE_37) in EPSG:2154
- SHAPEFILE_13: SHAPEFILE from $(SourceDataset_SHAPEFILE_49) in EPSG:2154
- SHAPEFILE_18: SHAPEFILE from $(SourceDataset_SHAPEFILE_34) in EPSG:2154
- SHAPEFILE_19: SHAPEFILE from $(SourceDataset_SHAPEFILE_36) in EPSG:2154
- SHAPEFILE_20: SHAPEFILE from $(SourceDataset_SHAPEFILE_38) in EPSG:2154
- SHAPEFILE_21: SHAPEFILE from $(SourceDataset_SHAPEFILE_40) in EPSG:2154

Bookmark: ADMINSITRATIF
COMMUNE (reader SHAPEFILE_25)
    attributes: ID varchar(24), INSEE_COM varchar(5), INSEE_ARR varchar(5), INSEE_COL varchar(5), INSEE_DEP varchar(5), INSEE_REG varchar(5), POPULATION long, SURFACE_HA long, DATE_CREAT varchar(19), DATE_MAJ varchar(19), DATE_APP date, DATE_CONF date, CODE_POST varchar(5), NOM varchar(80), CL_ARROND varchar(3), CL_COLLTER varchar(3), CL_DEPART varchar(3), CL_REGION varchar(3), CAPITALE varchar(3), DATE_RCT date, RECENSEUR varchar(16), SIREN_EPCI varchar(32), ID_CH_LIEU varchar(24), ID_AUT_ADM varchar(254), CODE_SIREN varchar(9)
    -> DuplicateFilter-COMMUNE
DuplicateFilter-COMMUNE
    INPUT_ORDERED_CHOICE = No
    KEYATTR = INSEE_COM
    UNIQUE -> 2DForcer-COMMUNE
2DForcer-COMMUNE
    2D -> Reprojector-COMMUNE
Reprojector-COMMUNE
    DEST = EPSG:4326
    INTERPOLATION_TYPE_NAME = Nearest Neighbor
    RASTER_CELL_SIZE = Preserve Cells
    RASTER_TOLERANCE = 0.0
    SOURCE = EPSG:2154
    REPROJECTED -> FeatureJoiner [LEFT]
ZONE_D_HABITATION (reader SHAPEFILE_1)
    attributes: ID varchar(24), NATURE varchar(18), NAT_DETAIL varchar(18), TOPONYME varchar(127), STATUT_TOP varchar(10), IMPORTANCE varchar(1), FICTIF varchar(3), ETAT varchar(15), DATE_CREAT varchar(19), DATE_MAJ varchar(19), DATE_APP date, DATE_CONF date, SOURCE varchar(127), ID_SOURCE varchar(254), ACQU_PLANI varchar(32), PREC_PLANI float, ID_BAN varchar(12)
    -> 2DForcer-ZoneHabitation
2DForcer-ZoneHabitation
    2D -> Reprojector-ZoneHabitation
Reprojector-ZoneHabitation
    DEST = EPSG:4326
    INTERPOLATION_TYPE_NAME = Nearest Neighbor
    RASTER_CELL_SIZE = Preserve Cells
    RASTER_TOLERANCE = 0.0
    SOURCE = EPSG:2154
    REPROJECTED -> DuplicateFilter-ZoneHabitation
DuplicateFilter-ZoneHabitation
    INPUT_ORDERED_CHOICE = No
    KEYATTR = ID
    UNIQUE -> Tester-CHEFLIEU
    UNIQUE -> Tester-ZONEHABITATION
Note: Polygônes
Tester-ZONEHABITATION
    BOOL_OP = COMPOSITE
    COMPOSITE_TEST = 1 AND 2 AND 3
    TEST_CLAUSE:
      TEST @Value(IMPORTANCE) IN 1,2,3
      TEST @Value(NATURE) = Lieu-dit habité
      CASE_INSENSITIVE_TEST @Value(TOPONYME) NOT_BEGINS_WITH Commune d
    TEST_MODE = PER_TEST
    PASSED -> Generalizer-ZONEHABITATION
Generalizer-ZONEHABITATION
    ALG_TEXT = McMaster (Smooth)
    CLEANING_TOLERANCE = Automatic
    DISPLACEMENT = 25
    NUMNEIGHBORS = 2
    PRESERVE = Yes
    PRESERVE_PATHS = No
    -> AttributeKeeper-ZONEHABITATION
AttributeKeeper-ZONEHABITATION
    CREATE_BULK_MODE_FEATURES = NO
    KEEP_ATTRS = TOPONYME
    -> AttributeManager-ZONEHABITATION
AttributeManager-ZONEHABITATION
    ATTR_TABLE:
      RENAME_SET_VALUE TOPONYME > NAME
      SET_TO MP_TYPE = 0x03
      SET_TO EndLevel = 4
      SET_TO MPBITLEVEL = 20
    -> StringCaseChanger-ZONEHABITATION
StringCaseChanger-ZONEHABITATION
    ATTRCHOICE = Selected Attributes
    ATTRLIST = NAME
    CHANGE_TYPE = Full Title Case
    -> AttributeEncoder-ZONEHABITATION
AttributeEncoder-ZONEHABITATION
    ATTRCHOICE = All Attributes
    DEST_ENCODING = windows-1252
    TREAT_AS_BYTES = Honor Encoding
    -> Tester-ZONEHABITATION_2
Note: NON NULL
Tester-ZONEHABITATION_2
    BOOL_OP = OR
    TEST_CLAUSE = TEST MP_TYPE NOT_ATTRIBUTE_VALUE_NULL ""
    TEST_MODE = TEST
    PASSED -> FeatureWriter-ZONEHABITATION [Output]
FeatureWriter-ZONEHABITATION
    COORDSYS = EPSG:4326
    DATASET = $(OUTPUT_DATA_TERRITORY)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = windows-1252
    SHAPEFILE_ENFORCE_ATTRIBUTE_LIMIT = No
    SHAPEFILE_MEASURES_AS_Z = No
    SHAPEFILE_REQUIRE_FIRST_ATTRNAME_ALPHA = Yes
    SHAPEFILE_SPATIAL_INDEXES = BOTH
    SHAPEFILE_SURFACE_SOLID_STORAGE = PATCH
    TOTAL_FEATURES_WRITTEN_ATTR = _total_features_written
Note: Points
Tester-CHEFLIEU
    BOOL_OP = COMPOSITE
    COMPOSITE_TEST = 1 AND 2 AND 3
    TEST_CLAUSE:
      TEST @Value(IMPORTANCE) IN 1,2
      TEST @Value(NATURE) = Lieu-dit habité
      TEST @Value(ACQU_PLANI) = Calcul d'enveloppe urbaine
    TEST_MODE = TEST
    PASSED -> CenterPointExtractor-CHEFLIEU
CenterPointExtractor-CHEFLIEU
    CENTX = _inside_x
    CENTY = _inside_y
    CENTZ = _inside_z
    EXTRACTIONMODE = CENTEROFGRAV
    -> VertexCreator-CHEFLIEU
VertexCreator-CHEFLIEU
    MEASURE_TYPE = Continuous
    MODE_NAME = Replace with Point
    XVAL = @Value(_inside_x)
    YVAL = @Value(_inside_y)
    -> AttributeKeeper-CHEFLIEU
AttributeKeeper-CHEFLIEU
    CREATE_BULK_MODE_FEATURES = NO
    KEEP_ATTRS = TOPONYME,IMPORTANCE
    -> AttributeManager-CHEFLIEU
AttributeManager-CHEFLIEU
    ATTR_TABLE:
      RENAME_SET_VALUE TOPONYME > NAME
      SET_TO MP_TYPE = FME_CONDITIONAL:DEFAULT_VALUE'0x00800'BOOL_OP;OR;COMPOSITE_TEST;1;TEST @Value(IMPORTANCE) = 1'0x00200'BOOL_OP;OR;COMPOSITE_TEST;1;TEST @Value(IMPORTANCE) = 2'0x00800'FME_NUM_CONDITIONS3___
      SET_TO EndLevel = 7
      SET_TO MPBITLEVEL = 17
      REMOVE IMPORTANCE
    -> Clipper [CANDIDATE]
Note: INSEE : region_2022 [CSV2]
CSV (reader CSV2_1)
    attributes: REG uint32, CHEFLIEU varchar(6), TNCC uint32, NCC varchar(27), NCCENR varchar(28), LIBELLE varchar(28)
    -> FeatureJoiner [RIGHT]
Note: Jointure : nom des régions
FeatureJoiner
    ATTR_CONFLICT_RES = Prefer Left
    GEOMETRY_HANDLING = Prefer Left
    JOIN_KEYS = INSEE_REG REG AUTO
    JOIN_MODE = Inner
    JOINED -> AttributeKeeper-COMMUNE
AttributeKeeper-COMMUNE
    CREATE_BULK_MODE_FEATURES = NO
    KEEP_ATTRS = CODE_POST,NOM,NCCENR,INSEE_REG
    -> AttributeManager-COMMUNE
AttributeManager-COMMUNE
    ATTR_TABLE:
      RENAME_SET_VALUE NOM > NAME
      SET_TO MP_TYPE = 0x54
      SET_TO Country = France~[0x1d]FRA
      RENAME_SET_VALUE NCCENR > RegionName
      SET_TO CityName = @Value(NAME)
      RENAME_SET_VALUE CODE_POST > Zip
      SET_TO EndLevel = 7
      SET_TO MPBITLEVEL = 17
      REMOVE INSEE_REG
    -> AttributeEncoder-COMMUNE
    -> Junction_3
AttributeEncoder-COMMUNE
    ATTRCHOICE = All Attributes
    DEST_ENCODING = windows-1252
    TREAT_AS_BYTES = Honor Encoding
    -> Tester-COMMUNE
    -> Junction
Note: NON NULL
Tester-COMMUNE
    BOOL_OP = OR
    TEST_CLAUSE = TEST MP_TYPE NOT_ATTRIBUTE_VALUE_NULL ""
    TEST_MODE = TEST
    PASSED -> FeatureWriter-COMMUNE [garmin_bdtopo_surface_hydrographique]
FeatureWriter-COMMUNE
    COORDSYS = EPSG:4326
    DATASET = $(OUTPUT_DATA_TERRITORY)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = windows-1252
    SHAPEFILE_ENFORCE_ATTRIBUTE_LIMIT = No
    SHAPEFILE_MEASURES_AS_Z = No
    SHAPEFILE_REQUIRE_FIRST_ATTRNAME_ALPHA = Yes
    SHAPEFILE_SPATIAL_INDEXES = BOTH
    SHAPEFILE_SURFACE_SOLID_STORAGE = PATCH
    TOTAL_FEATURES_WRITTEN_ATTR = _total_features_written
Note: AttributeKeeper : Input
Junction
    -> Junction_2
Note: AttributeEncoder-COMMUNE : Output
Junction_2
    -> AttributeKeeper
AttributeKeeper
    CREATE_BULK_MODE_FEATURES = NO
    KEEP_ATTRS = CityName,Country,RegionName,Zip
    -> Clipper [CLIPPER]
Clipper
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> AttributeKeeper_2
AttributeKeeper_2
    CREATE_BULK_MODE_FEATURES = NO
    KEEP_ATTRS = CityName,Country,EndLevel,MP_TYPE,NAME,RegionName,Zip,MPBITLEVEL
    -> StringCaseChanger-CHEFLIEU
StringCaseChanger-CHEFLIEU
    ATTRCHOICE = Selected Attributes
    ATTRLIST = NAME
    CHANGE_TYPE = Full Title Case
    -> AttributeEncoder-CHEFLIEU
AttributeEncoder-CHEFLIEU
    ATTRCHOICE = All Attributes
    DEST_ENCODING = windows-1252
    TREAT_AS_BYTES = Honor Encoding
    -> Tester-CHEFLIEU_2
Note: NON NULL
Tester-CHEFLIEU_2
    BOOL_OP = OR
    TEST_CLAUSE = TEST MP_TYPE NOT_ATTRIBUTE_VALUE_NULL ""
    TEST_MODE = TEST
    PASSED -> FeatureWriter-CHEFLIEU [Output00]
FeatureWriter-CHEFLIEU
    COORDSYS = EPSG:4326
    DATASET = $(OUTPUT_DATA_TERRITORY)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = windows-1252
    SHAPEFILE_ENFORCE_ATTRIBUTE_LIMIT = No
    SHAPEFILE_MEASURES_AS_Z = No
    SHAPEFILE_REQUIRE_FIRST_ATTRNAME_ALPHA = Yes
    SHAPEFILE_SPATIAL_INDEXES = BOTH
    SHAPEFILE_SURFACE_SOLID_STORAGE = PATCH
    TOTAL_FEATURES_WRITTEN_ATTR = _total_features_written
Note: FeatureJoiner_2 : Right
Junction_3

Bookmark: HYDROGRAPHIE
TRONCON_HYDROGRAPHIQUE (reader SHAPEFILE_2)
    attributes: ID varchar(24), CODE_HYDRO varchar(19), CODE_PAYS varchar(8), NATURE varchar(27), FICTIF varchar(3), POS_SOL varchar(8), ETAT varchar(15), DATE_CREAT varchar(19), DATE_MAJ varchar(19), DATE_APP date, DATE_CONF date, SOURCE varchar(127), ID_SOURCE varchar(254), ACQU_PLANI varchar(32), PREC_PLANI float, ACQU_ALTI varchar(30), PREC_ALTI float, SRC_COORD varchar(31), SRC_ALTI varchar(41), STATUT varchar(7), PERSISTANC varchar(12), FOSSE varchar(3), NAVIGABL varchar(3), SALINITE varchar(3), NUM_ORDRE varchar(2), CLA_ORDRE varchar(32), ORIGINE varchar(24), PER_ORDRE varchar(32), SENS_ECOUL varchar(12), RES_COULAN varchar(3),
      DELIMIT varchar(3), LARGEUR varchar(26), BRAS varchar(10), COMMENT varchar(80), CODE_CARTH varchar(8), ID_C_EAU varchar(254), ID_S_HYDRO varchar(254), ID_ENT_TR varchar(24), NOM_C_EAU varchar(120), NOM_ENT_TR varchar(120)
    -> DuplicateFilter-TRONCON_HYDROGRAPHIQUE
DuplicateFilter-TRONCON_HYDROGRAPHIQUE
    INPUT_ORDERED_CHOICE = No
    KEYATTR = ID
    UNIQUE -> 2DForcer-TRONCON_HYDROGRAPHIQUE
2DForcer-TRONCON_HYDROGRAPHIQUE
    2D -> Reprojector-TRONCON_HYDROGRAPHIQUE
Reprojector-TRONCON_HYDROGRAPHIQUE
    DEST = EPSG:4326
    INTERPOLATION_TYPE_NAME = Nearest Neighbor
    RASTER_CELL_SIZE = Preserve Cells
    RASTER_TOLERANCE = 0.0
    SOURCE = EPSG:2154
    REPROJECTED -> AttributeKeeper-TRONCON_HYDROGRAPHIQUE
AttributeKeeper-TRONCON_HYDROGRAPHIQUE
    CREATE_BULK_MODE_FEATURES = NO
    KEEP_ATTRS = NOM_C_EAU,PERSISTANC
    -> AttributeManager-TRONCON_HYDROGRAPHIQUE
AttributeManager-TRONCON_HYDROGRAPHIQUE
    ATTR_TABLE:
      RENAME_SET_VALUE NOM_C_EAU > NAME = FME_CONDITIONAL:DEFAULT_VALUE'@Value(NAME)'BOOL_OP;OR;COMPOSITE_TEST;1;TEST NAME ATTRIBUTE_IS_MISSING _FME_BLANK_STRING_'FME_NULL_VALUE'FME_NUM_CONDITIONS2___
      SET_TO MP_TYPE = FME_CONDITIONAL:DEFAULT_VALUE'0x18'BOOL_OP;OR;COMPOSITE_TEST;1;TEST @Value(PERSISTANC) = Permanent'0x18'BOOL_OP;OR;COMPOSITE_TEST;1;TEST @Value(PERSISTANC) = Intermittent'0x26'FME_NUM_CONDITIONS3___
      SET_TO EndLevel = 2
      SET_TO MPBITLEVEL = 22
      REMOVE PERSISTANC
    -> StringCaseChanger-TRONCON_HYDROGRAPHIQUE
StringCaseChanger-TRONCON_HYDROGRAPHIQUE
    ATTRCHOICE = Selected Attributes
    ATTRLIST = NAME
    CHANGE_TYPE = Full Title Case
    -> AttributeEncoder-TRONCON_HYDROGRAPHIQUE
AttributeEncoder-TRONCON_HYDROGRAPHIQUE
    ATTRCHOICE = All Attributes
    DEST_ENCODING = windows-1252
    TREAT_AS_BYTES = Honor Encoding
    -> Tester-TRONCON_HYDROGRAPHIQUE
Note: NON NULL
Tester-TRONCON_HYDROGRAPHIQUE
    BOOL_OP = OR
    TEST_CLAUSE = TEST MP_TYPE NOT_ATTRIBUTE_VALUE_NULL ""
    TEST_MODE = TEST
    PASSED -> FeatureWriter-TRONCON_HYDROGRAPHIQUE [Output00]
FeatureWriter-TRONCON_HYDROGRAPHIQUE
    COORDSYS = EPSG:4326
    DATASET = $(OUTPUT_DATA_TERRITORY)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = windows-1252
    SHAPEFILE_ENFORCE_ATTRIBUTE_LIMIT = No
    SHAPEFILE_MEASURES_AS_Z = No
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
SURFACE_HYDROGRAPHIQUE (reader SHAPEFILE_3)
    attributes: ID varchar(24), CODE_HYDRO varchar(19), CODE_PAYS varchar(8), NATURE varchar(27), POS_SOL varchar(2), ETAT varchar(15), DATE_CREAT varchar(19), DATE_MAJ varchar(19), DATE_APP date, DATE_CONF date, SOURCE varchar(127), ID_SOURCE varchar(254), ACQU_PLANI varchar(32), PREC_PLANI float, ACQU_ALTI varchar(30), PREC_ALTI float, SRC_COORD varchar(31), SRC_ALTI varchar(41), STATUT varchar(7), PERSISTANC varchar(12), SALINITE varchar(3), ORIGINE varchar(24), COMMENT varchar(80), ID_P_EAU varchar(254), ID_C_EAU varchar(254), ID_ENT_TR varchar(24), NOM_P_EAU varchar(120), NOM_C_EAU varchar(120), NOM_ENT_TR varchar(120)
    -> DuplicateFilter-SURFACE_HYDROGRAPHIQUE
DuplicateFilter-SURFACE_HYDROGRAPHIQUE
    INPUT_ORDERED_CHOICE = No
    KEYATTR = ID
    UNIQUE -> 2DForcer-SURFACE_HYDROGRAPHIQUE
2DForcer-SURFACE_HYDROGRAPHIQUE
    2D -> Reprojector-SURFACE_HYDROGRAPHIQUE
Reprojector-SURFACE_HYDROGRAPHIQUE
    DEST = EPSG:4326
    INTERPOLATION_TYPE_NAME = Nearest Neighbor
    RASTER_CELL_SIZE = Preserve Cells
    RASTER_TOLERANCE = 0.0
    SOURCE = EPSG:2154
    REPROJECTED -> AttributeKeeper-SURFACE_HYDROGRAPHIQUE
AttributeKeeper-SURFACE_HYDROGRAPHIQUE
    CREATE_BULK_MODE_FEATURES = NO
    KEEP_ATTRS = NATURE,NOM_P_EAU,PERSISTANC
    -> AttributeManager-SURFACE_HYDROGRAPHIQUE
AttributeManager-SURFACE_HYDROGRAPHIQUE
    ATTR_TABLE:
      RENAME_SET_VALUE NOM_P_EAU > NAME = FME_CONDITIONAL:DEFAULT_VALUE'@Value(NAME)'BOOL_OP;OR;COMPOSITE_TEST;1;TEST NAME ATTRIBUTE_IS_MISSING _FME_BLANK_STRING_'FME_NULL_VALUE'FME_NUM_CONDITIONS2___
      SET_TO MP_TYPE = FME_CONDITIONAL:DEFAULT_VALUE'0x3f'BOOL_OP;AND;COMPOSITE_TEST;1 AND 2;TEST @Value(PERSISTANC) = Permanent;TEST @Value(NATURE) != Glacier, névé'0x3f'BOOL_OP;AND;COMPOSITE_TEST;1 AND 2;TEST @Value(PERSISTANC) = Intermittent;TEST @Value(NATURE) != Glacier, névé'0x4c'BOOL_OP;AND;COMPOSITE_TEST;1 AND 2;TEST @Value(PERSISTANC) = Inconnue;TEST @Value(NATURE) != Glacier, névé'0x4c'BOOL_OP;OR;COMPOSITE_TEST;1;TEST @Value(NATURE) = Glacier, névé'0x4d'FME_NUM_CONDITIONS5___
      SET_TO EndLevel = 2
      SET_TO MPBITLEVEL = 22
      REMOVE NATURE
      REMOVE PERSISTANC
    -> AttributeEncoder-SURFACE_HYDROGRAPHIQUE
AttributeEncoder-SURFACE_HYDROGRAPHIQUE
    ATTRCHOICE = All Attributes
    DEST_ENCODING = windows-1252
    TREAT_AS_BYTES = Honor Encoding
    -> Tester-SURFACE_HYDROGRAPHIQUE
Note: NON NULL
Tester-SURFACE_HYDROGRAPHIQUE
    BOOL_OP = OR
    TEST_CLAUSE = TEST MP_TYPE NOT_ATTRIBUTE_VALUE_NULL ""
    TEST_MODE = TEST
    PASSED -> FeatureWriter-SURFACE_HYDROGRAPHIQUE [Output]
FeatureWriter-SURFACE_HYDROGRAPHIQUE
    COORDSYS = EPSG:4326
    DATASET = $(OUTPUT_DATA_TERRITORY)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = windows-1252
    SHAPEFILE_ENFORCE_ATTRIBUTE_LIMIT = No
    SHAPEFILE_MEASURES_AS_Z = No
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
DETAIL_HYDROGRAPHIQUE (reader SHAPEFILE_4)
    attributes: ID varchar(24), NATURE varchar(15), NAT_DETAIL varchar(18), PERSISTANC varchar(15), TOPONYME varchar(127), STATUT_TOP varchar(10), IMPORTANCE varchar(1), ETAT varchar(15), DATE_CREAT varchar(19), DATE_MAJ varchar(19), DATE_APP date, DATE_CONF date, SOURCE varchar(127), ID_SOURCE varchar(254), ACQU_PLANI varchar(32), PREC_PLANI float, ID_BAN varchar(12)
    -> DuplicateFilter-DETAIL_HYDROGRAPHIQUE
DuplicateFilter-DETAIL_HYDROGRAPHIQUE
    INPUT_ORDERED_CHOICE = No
    KEYATTR = ID
    UNIQUE -> 2DForcer-DETAIL_HYDROGRAPHIQUE
2DForcer-DETAIL_HYDROGRAPHIQUE
    2D -> Reprojector-DETAIL_HYDROGRAPHIQUE
Reprojector-DETAIL_HYDROGRAPHIQUE
    DEST = EPSG:4326
    INTERPOLATION_TYPE_NAME = Nearest Neighbor
    RASTER_CELL_SIZE = Preserve Cells
    RASTER_TOLERANCE = 0.0
    SOURCE = EPSG:2154
    REPROJECTED -> AttributeKeeper-DETAIL_HYDROGRAPHIQUE
AttributeKeeper-DETAIL_HYDROGRAPHIQUE
    CREATE_BULK_MODE_FEATURES = NO
    KEEP_ATTRS = NAT_DETAIL,NATURE,TOPONYME
    -> AttributeManager-DETAIL_HYDROGRAPHIQUE
AttributeManager-DETAIL_HYDROGRAPHIQUE
    ATTR_TABLE:
      SET_TO NAME = FME_CONDITIONAL:DEFAULT_VALUE'@Value(NATURE)'BOOL_OP;OR;COMPOSITE_TEST;1;TEST TOPONYME NOT_ATTRIBUTE_IS_MISSING _FME_BLANK_STRING_'@Value(TOPONYME)'BOOL_OP;AND;COMPOSITE_TEST;1 AND 2;TEST TOPONYME ATTRIBUTE_IS_MISSING _FME_BLANK_STRING_;TEST NAT_DETAIL NOT_ATTRIBUTE_IS_MISSING _FME_BLANK_STRING_'@Value(NATURE) - @Value(NAT_DETAIL)'FME_NUM_CONDITIONS3___
      SET_TO MP_TYPE = FME_CONDITIONAL:DEFAULT_VALUE'0x06414'BOOL_OP;OR;COMPOSITE_TEST;1;TEST @Value(NATURE) = Arroyo'0x06501'BOOL_OP;OR;COMPOSITE_TEST;1;TEST @Value(NATURE) = Baie'0x06503'BOOL_OP;OR;COMPOSITE_TEST;1;TEST @Value(NATURE) = Cascade'0x06508'BOOL_OP;OR;COMPOSITE_TEST;1;TEST @Value(NATURE) = Citerne'0x06414'BOOL_OP;OR;COMPOSITE_TEST;1;TEST @Value(NATURE) = Crique'0x06507'BOOL_OP;OR;COMPOSITE_TEST;1;TEST @Value(NATURE) = Fontaine'0x06509'BOOL_OP;OR;COMPOSITE_TEST;1;TEST @Value(NATURE) = Glacier'0x0650a'BOOL_OP;OR;COMPOSITE_TEST;1;TEST @Value(NATURE) = Lac'0x0650d'BOOL_OP;OR;COMPOSITE_TEST;1;TEST @Value(NATURE) = Lavoir'0x06414'BOOL_OP;OR;COMPOSITE_TEST;1;TEST @Value(NATURE) = Marais'0x06513'BOOL_OP;OR;COMPOSITE_TEST;1;TEST @Value(NATURE) = Mer'0x06510'BOOL_OP;OR;COMPOSITE_TEST;1;TEST @Value(NATURE) = Perte'0x06414'BOOL_OP;OR;COMPOSITE_TEST;1;TEST @Value(NATURE) = Point d'eau'0x06414'BOOL_OP;OR;COMPOSITE_TEST;1;TEST @Value(NATURE) = Réservoir'0x0650f'BOOL_OP;OR;COMPOSITE_TEST;1;TEST @Value(NATURE) = Résurgence'0x06414'BOOL_OP;OR;COMPOSITE_TEST;1;TEST @Value(NATURE) = Source'0x06511'BOOL_OP;OR;COMPOSITE_TEST;1;TEST @Value(NATURE) = Source captée'0x06511'FME_NUM_CONDITIONS18___
      SET_TO EndLevel = 2
      SET_TO MPBITLEVEL = 22
      REMOVE NATURE
      REMOVE NAT_DETAIL
      REMOVE TOPONYME
    -> AttributeEncoder-DETAIL_HYDROGRAPHIQUE
AttributeEncoder-DETAIL_HYDROGRAPHIQUE
    ATTRCHOICE = All Attributes
    DEST_ENCODING = windows-1252
    TREAT_AS_BYTES = Honor Encoding
    -> Tester-DETAIL_HYDROGRAPHIQUE
Note: NON NULL
Tester-DETAIL_HYDROGRAPHIQUE
    BOOL_OP = OR
    TEST_CLAUSE = TEST MP_TYPE NOT_ATTRIBUTE_VALUE_NULL ""
    TEST_MODE = TEST
    PASSED -> FeatureWriter-DETAIL_HYDROGRAPHIQUE [Output00]
FeatureWriter-DETAIL_HYDROGRAPHIQUE
    COORDSYS = EPSG:4326
    DATASET = $(OUTPUT_DATA_TERRITORY)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = windows-1252
    SHAPEFILE_ENFORCE_ATTRIBUTE_LIMIT = No
    SHAPEFILE_MEASURES_AS_Z = No
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
TOPONYMIE_HYDROGRAPHIE (reader SHAPEFILE_5)
    attributes: ID varchar(24), CLASSE varchar(32), NATURE varchar(50), GRAPHIE varchar(165), SOURCE varchar(127), STATUT_TOP varchar(10), DATE_TOP date, LANGUE varchar(10)
    -> DuplicateFilter-TOPONYMIE_HYDROGRAPHIE
DuplicateFilter-TOPONYMIE_HYDROGRAPHIE
    INPUT_ORDERED_CHOICE = No
    KEYATTR = ID
    UNIQUE -> 2DForcer-TOPONYMIE_HYDROGRAPHIE
2DForcer-TOPONYMIE_HYDROGRAPHIE
    2D -> Reprojector-TOPONYMIE_HYDROGRAPHIE
Reprojector-TOPONYMIE_HYDROGRAPHIE
    DEST = EPSG:4326
    INTERPOLATION_TYPE_NAME = Nearest Neighbor
    RASTER_CELL_SIZE = Preserve Cells
    RASTER_TOLERANCE = 0.0
    SOURCE = EPSG:2154
    REPROJECTED -> AttributeKeeper-TOPONYMIE_HYDROGRAPHIE
AttributeKeeper-TOPONYMIE_HYDROGRAPHIE
    CREATE_BULK_MODE_FEATURES = NO
    KEEP_ATTRS = GRAPHIE,NATURE
    -> AttributeManager-TOPONYMIE_HYDROGRAPHIE
AttributeManager-TOPONYMIE_HYDROGRAPHIE
    ATTR_TABLE:
      RENAME_SET_VALUE GRAPHIE > NAME
      SET_TO MP_TYPE = FME_CONDITIONAL:DEFAULT_VALUE'0x06414'BOOL_OP;OR;COMPOSITE_TEST;1;TEST @Value(NATURE) = Baie'0x06503'BOOL_OP;OR;COMPOSITE_TEST;1;TEST @Value(NATURE) = Canal'0x06506'BOOL_OP;OR;COMPOSITE_TEST;1;TEST @Value(NATURE) = Cascade'0x06508'BOOL_OP;OR;COMPOSITE_TEST;1;TEST @Value(NATURE) = Citerne'0x06414'BOOL_OP;OR;COMPOSITE_TEST;1;TEST @Value(NATURE) = Crique'0x06507'BOOL_OP;OR;COMPOSITE_TEST;1;TEST @Value(NATURE) = Ecoulement naturel'0x06414'BOOL_OP;OR;COMPOSITE_TEST;1;TEST @Value(NATURE) = Embouchure'0x06414'BOOL_OP;OR;COMPOSITE_TEST;1;TEST @Value(NATURE) = Exutoire'0x06414'BOOL_OP;OR;COMPOSITE_TEST;1;TEST @Value(NATURE) = Fontaine'0x06509'BOOL_OP;OR;COMPOSITE_TEST;1;TEST @Value(NATURE) = Glacier, névé'0x0650a'BOOL_OP;OR;COMPOSITE_TEST;1;TEST @Value(NATURE) = Lac'0x0650d'BOOL_OP;OR;COMPOSITE_TEST;1;TEST @Value(NATURE) = Lavoir'0x06414'BOOL_OP;OR;COMPOSITE_TEST;1;TEST @Value(NATURE) = Marais'0x06513'BOOL_OP;OR;COMPOSITE_TEST;1;TEST @Value(NATURE) = Mare'0x06513'BOOL_OP;OR;COMPOSITE_TEST;1;TEST @Value(NATURE) = Mer'0x06510'BOOL_OP;OR;COMPOSITE_TEST;1;TEST @Value(NATURE) = Perte'0x06414'BOOL_OP;OR;COMPOSITE_TEST;1;TEST @Value(NATURE) = Plan d'eau de gravière'0x06414'BOOL_OP;OR;COMPOSITE_TEST;1;TEST @Value(NATURE) = Point d'eau'0x06414'BOOL_OP;OR;COMPOSITE_TEST;1;TEST @Value(NATURE) = Réservoir-bassin'0x0650f'BOOL_OP;OR;COMPOSITE_TEST;1;TEST @Value(NATURE) = Réservoir-bassin piscicole'0x0650f'BOOL_OP;OR;COMPOSITE_TEST;1;TEST @Value(NATURE) = Réservoir'0x0650f'BOOL_OP;OR;COMPOSITE_TEST;1;TEST @Value(NATURE) = Retenue'0x0650f'BOOL_OP;OR;COMPOSITE_TEST;1;TEST @Value(NATURE) = Retenue-barrage'0x0650f'BOOL_OP;OR;COMPOSITE_TEST;1;TEST @Value(NATURE) = Retenue-barrage'0x0650f'BOOL_OP;OR;COMPOSITE_TEST;1;TEST @Value(NATURE) = Retenue-digue'0x0650f'BOOL_OP;OR;COMPOSITE_TEST;1;TEST @Value(NATURE) = Source'0x06511'BOOL_OP;OR;COMPOSITE_TEST;1;TEST @Value(NATURE) = Source captée'0x06511'FME_NUM_CONDITIONS28___
      SET_TO EndLevel = 2
      SET_TO MPBITLEVEL = 22
      REMOVE NATURE
    -> StringCaseChanger-TOPONYMIE_HYDROGRAPHIE
StringCaseChanger-TOPONYMIE_HYDROGRAPHIE
    ATTRCHOICE = Selected Attributes
    ATTRLIST = NAME
    CHANGE_TYPE = Full Title Case
    -> AttributeEncoder-TOPONYMIE_HYDROGRAPHIE
AttributeEncoder-TOPONYMIE_HYDROGRAPHIE
    ATTRCHOICE = All Attributes
    DEST_ENCODING = windows-1252
    TREAT_AS_BYTES = Honor Encoding
    -> Tester-TOPONYMIE_HYDROGRAPHIE
Note: NON NULL
Tester-TOPONYMIE_HYDROGRAPHIE
    BOOL_OP = OR
    TEST_CLAUSE = TEST MP_TYPE NOT_ATTRIBUTE_VALUE_NULL ""
    TEST_MODE = TEST
    PASSED -> FeatureWriter-TOPONYMIE_HYDROGRAPHIE [Output00]
FeatureWriter-TOPONYMIE_HYDROGRAPHIE
    COORDSYS = EPSG:4326
    DATASET = $(OUTPUT_DATA_TERRITORY)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = windows-1252
    SHAPEFILE_ENFORCE_ATTRIBUTE_LIMIT = No
    SHAPEFILE_MEASURES_AS_Z = No
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written

Bookmark: TOPONYMIE
TOPONYMIE_LIEUX_NOMMES (reader SHAPEFILE_13)
    attributes: ID varchar(24), CLASSE varchar(32), NATURE varchar(50), GRAPHIE varchar(165), SOURCE varchar(127), STATUT_TOP varchar(10), DATE_TOP date, LANGUE varchar(10)
    -> DuplicateFilter-TOPONYMIE_LIEUX_NOMMES
DuplicateFilter-TOPONYMIE_LIEUX_NOMMES
    INPUT_ORDERED_CHOICE = No
    KEYATTR = ID
    UNIQUE -> 2DForcer-TOPONYMIE_LIEUX_NOMMES
2DForcer-TOPONYMIE_LIEUX_NOMMES
    2D -> Reprojector-TOPONYMIE_LIEUX_NOMMES
Reprojector-TOPONYMIE_LIEUX_NOMMES
    DEST = EPSG:4326
    INTERPOLATION_TYPE_NAME = Nearest Neighbor
    RASTER_CELL_SIZE = Preserve Cells
    RASTER_TOLERANCE = 0.0
    SOURCE = EPSG:2154
    REPROJECTED -> AttributeKeeper-TOPONYMIE_LIEUX_NOMMES
AttributeKeeper-TOPONYMIE_LIEUX_NOMMES
    CREATE_BULK_MODE_FEATURES = NO
    KEEP_ATTRS = GRAPHIE,NATURE
    -> AttributeManager-TOPONYMIE_LIEUX_NOMMES
AttributeManager-TOPONYMIE_LIEUX_NOMMES
    ATTR_TABLE:
      RENAME_SET_VALUE GRAPHIE > NAME = FME_CONDITIONAL:DEFAULT_VALUE'@Value(NAME)'BOOL_OP;OR;COMPOSITE_TEST;1;TEST NAME ATTRIBUTE_IS_MISSING _FME_BLANK_STRING_'FME_NULL_VALUE'FME_NUM_CONDITIONS2___
      SET_TO MP_TYPE = FME_CONDITIONAL:DEFAULT_VALUE'FME_NULL_VALUE'BOOL_OP;OR;COMPOSITE_TEST;1;TEST @Value(NATURE) = Arbre'0x1150c'BOOL_OP;OR;COMPOSITE_TEST;1;TEST @Value(NATURE) = Bois'0x0660a'BOOL_OP;OR;COMPOSITE_TEST;1;TEST @Value(NATURE) = Château'0x1150f'BOOL_OP;OR;COMPOSITE_TEST;1;TEST @Value(NATURE) = Cirque'0x06608'BOOL_OP;OR;COMPOSITE_TEST;1;TEST @Value(NATURE) = Col'0x06601'BOOL_OP;OR;COMPOSITE_TEST;1;TEST @Value(NATURE) = Crête'0x06613'BOOL_OP;OR;COMPOSITE_TEST;1;TEST @Value(NATURE) = Dépression'0x0660b'BOOL_OP;OR;COMPOSITE_TEST;1;TEST @Value(NATURE) = Escarpement'0x06607'BOOL_OP;OR;COMPOSITE_TEST;1;TEST @Value(NATURE) = Gorge'0x06611'BOOL_OP;OR;COMPOSITE_TEST;1;TEST @Value(NATURE) = Gouffre'0x11515'BOOL_OP;OR;COMPOSITE_TEST;1;TEST @Value(NATURE) = Grange'0x11510'BOOL_OP;OR;COMPOSITE_TEST;1;TEST @Value(NATURE) = Grotte'0x11515'BOOL_OP;OR;COMPOSITE_TEST;1;TEST @Value(NATURE) = Ile'0x06501'BOOL_OP;OR;COMPOSITE_TEST;1;TEST @Value(NATURE) = Lieu-dit habité'0x00d'BOOL_OP;OR;COMPOSITE_TEST;1;TEST @Value(NATURE) = Lieu-dit non habité'0x1150e'BOOL_OP;OR;COMPOSITE_TEST;1;TEST @Value(NATURE) = Montagne'0x06601'BOOL_OP;OR;COMPOSITE_TEST;1;TEST @Value(NATURE) = Moulin'0x11512'BOOL_OP;OR;COMPOSITE_TEST;1;TEST @Value(NATURE) = Pic'0x06616'BOOL_OP;OR;COMPOSITE_TEST;1;TEST @Value(NATURE) = Plage'0x1160e'BOOL_OP;OR;COMPOSITE_TEST;1;TEST @Value(NATURE) = Plaine'0x06610'BOOL_OP;OR;COMPOSITE_TEST;1;TEST @Value(NATURE) = Quartier'0x11513'BOOL_OP;OR;COMPOSITE_TEST;1;TEST @Value(NATURE) = Rochers'0x06614'BOOL_OP;OR;COMPOSITE_TEST;1;TEST @Value(NATURE) = Ruines'0x11514'BOOL_OP;OR;COMPOSITE_TEST;1;TEST @Value(NATURE) = Sommet'0x06616'BOOL_OP;OR;COMPOSITE_TEST;1;TEST @Value(NATURE) = Vallée'0x06617'BOOL_OP;OR;COMPOSITE_TEST;1;TEST @Value(NATURE) = Versant'0x06615'BOOL_OP;OR;COMPOSITE_TEST;1;TEST @Value(NATURE) = Volcan'0x06608'BOOL_OP;OR;COMPOSITE_TEST;1;TEST @Value(NATURE) = Cap'0x06606'FME_NUM_CONDITIONS29___
      SET_TO EndLevel = 3
      SET_TO MPBITLEVEL = 21
      REMOVE NATURE
    -> StringCaseChanger-TOPONYMIE_LIEUX_NOMMES
StringCaseChanger-TOPONYMIE_LIEUX_NOMMES
    ATTRCHOICE = Selected Attributes
    ATTRLIST = NAME
    CHANGE_TYPE = Full Title Case
    -> AttributeEncoder-TOPONYMIE_LIEUX_NOMMES
AttributeEncoder-TOPONYMIE_LIEUX_NOMMES
    ATTRCHOICE = All Attributes
    DEST_ENCODING = windows-1252
    TREAT_AS_BYTES = Honor Encoding
    -> Tester-TOPONYMIE_LIEUX_NOMMES
Note: NON NULL
Tester-TOPONYMIE_LIEUX_NOMMES
    BOOL_OP = OR
    TEST_CLAUSE = TEST MP_TYPE NOT_ATTRIBUTE_VALUE_NULL ""
    TEST_MODE = TEST
    PASSED -> FeatureWriter-TOPONYMIE_LIEUX_NOMMES [Output03]
FeatureWriter-TOPONYMIE_LIEUX_NOMMES
    COORDSYS = EPSG:4326
    DATASET = $(OUTPUT_DATA_TERRITORY)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = windows-1252
    SHAPEFILE_ENFORCE_ATTRIBUTE_LIMIT = No
    SHAPEFILE_MEASURES_AS_Z = No
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written

Bookmark: SERVICES_ET_ACTIVITES
TOPONYMIE_SERVICES_ET_ACTIVITES (reader SHAPEFILE_18)
    attributes: ID varchar(24), CLASSE varchar(32), NATURE varchar(50), GRAPHIE varchar(165), SOURCE varchar(127), STATUT_TOP varchar(10), DATE_TOP date, LANGUE varchar(10)
    -> DuplicateFilter-TOPONYMIE_SERVICES_ET_ACTIVITES
DuplicateFilter-TOPONYMIE_SERVICES_ET_ACTIVITES
    INPUT_ORDERED_CHOICE = No
    KEYATTR = ID
    UNIQUE -> 2DForcer-TOPONYMIE_SERVICES_ET_ACTIVITES
2DForcer-TOPONYMIE_SERVICES_ET_ACTIVITES
    2D -> Reprojector-TOPONYMIE_SERVICES_ET_ACTIVITES
Reprojector-TOPONYMIE_SERVICES_ET_ACTIVITES
    DEST = EPSG:4326
    INTERPOLATION_TYPE_NAME = Nearest Neighbor
    RASTER_CELL_SIZE = Preserve Cells
    RASTER_TOLERANCE = 0.0
    SOURCE = EPSG:2154
    REPROJECTED -> AttributeKeeper-TOPONYMIE_SERVICES_ET_ACTIVITES
AttributeKeeper-TOPONYMIE_SERVICES_ET_ACTIVITES
    CREATE_BULK_MODE_FEATURES = NO
    KEEP_ATTRS = GRAPHIE,NATURE
    -> AttributeManager-TOPONYMIE_SERVICES_ET_ACTIVITES
AttributeManager-TOPONYMIE_SERVICES_ET_ACTIVITES
    ATTR_TABLE:
      RENAME_SET_VALUE GRAPHIE > NAME
      SET_TO MP_TYPE = FME_CONDITIONAL:DEFAULT_VALUE'FME_NULL_VALUE'BOOL_OP;OR;COMPOSITE_TEST;1;TEST @Value(NATURE) = Abri de montagne'0x02b04'BOOL_OP;OR;COMPOSITE_TEST;1;TEST @Value(NATURE) = Administration centrale de l'Etat'0x03007'BOOL_OP;OR;COMPOSITE_TEST;1;TEST @Value(NATURE) = Aire d'accueil des gens du voyage'0x02f0c'BOOL_OP;OR;COMPOSITE_TEST;1;TEST @Value(NATURE) = Aire de détente'0x02c04'BOOL_OP;OR;COMPOSITE_TEST;1;TEST @Value(NATURE) = Aquaculture'0x02900'BOOL_OP;OR;COMPOSITE_TEST;1;TEST @Value(NATURE) = Autre équipement sportif'0x11601'BOOL_OP;OR;COMPOSITE_TEST;1;TEST @Value(NATURE) = Autre établissement d'enseignement'0x02c05'BOOL_OP;OR;COMPOSITE_TEST;1;TEST @Value(NATURE) = Autre service déconcentré de l'Etat'0x03007'BOOL_OP;OR;COMPOSITE_TEST;1;TEST @Value(NATURE) = Baignade surveillée'0x1151f'BOOL_OP;OR;COMPOSITE_TEST;1;TEST @Value(NATURE) = Borne'0x0660f'BOOL_OP;OR;COMPOSITE_TEST;1;TEST @Value(NATURE) = Borne frontière'0x0660f'BOOL_OP;OR;COMPOSITE_TEST;1;TEST @Value(NATURE) = Camp militaire non clos'0x0640b'BOOL_OP;OR;COMPOSITE_TEST;1;TEST @Value(NATURE) = Camping'0x02b03'BOOL_OP;OR;COMPOSITE_TEST;1;TEST @Value(NATURE) = Capitainerie'0x02f09'BOOL_OP;OR;COMPOSITE_TEST;1;TEST @Value(NATURE) = Carrière'0x0640c'BOOL_OP;OR;COMPOSITE_TEST;1;TEST @Value(NATURE) = Caserne'0x03008'BOOL_OP;OR;COMPOSITE_TEST;1;TEST @Value(NATURE) = Caserne de pompiers'0x03008'BOOL_OP;OR;COMPOSITE_TEST;1;TEST @Value(NATURE) = Centrale électrique'0x02900'BOOL_OP;OR;COMPOSITE_TEST;1;TEST @Value(NATURE) = Centre de documentation'0x02c03'BOOL_OP;OR;COMPOSITE_TEST;1;TEST @Value(NATURE) = Centre équestre'0x02d0a'BOOL_OP;OR;COMPOSITE_TEST;1;TEST @Value(NATURE) = Champ de tir'0x0640b'BOOL_OP;OR;COMPOSITE_TEST;1;TEST @Value(NATURE) = Collège'0x02c05'BOOL_OP;OR;COMPOSITE_TEST;1;TEST @Value(NATURE) = Complexe sportif couvert'0x11601'BOOL_OP;OR;COMPOSITE_TEST;1;TEST @Value(NATURE) = Construction'0x06402'BOOL_OP;OR;COMPOSITE_TEST;1;TEST @Value(NATURE) = Culte chrétien'0x02c0e'BOOL_OP;OR;COMPOSITE_TEST;1;TEST @Value(NATURE) = Culte divers'0x02c0b'BOOL_OP;OR;COMPOSITE_TEST;1;TEST @Value(NATURE) = Culte israélite'0x02c10'BOOL_OP;OR;COMPOSITE_TEST;1;TEST @Value(NATURE) = Culte musulman'0x02c0d'BOOL_OP;OR;COMPOSITE_TEST;1;TEST @Value(NATURE) = Déchèterie'0x02900'BOOL_OP;OR;COMPOSITE_TEST;1;TEST @Value(NATURE) = Départ de ski de fond'0x02f0b'BOOL_OP;OR;COMPOSITE_TEST;1;TEST @Value(NATURE) = Divers agricole'0x1150e'BOOL_OP;OR;COMPOSITE_TEST;1;TEST @Value(NATURE) = Divers commercial'0x02e04'BOOL_OP;OR;COMPOSITE_TEST;1;TEST @Value(NATURE) = Divers industriel'0x02900'BOOL_OP;OR;COMPOSITE_TEST;1;TEST @Value(NATURE) = Divers public ou administratif'0x03007'BOOL_OP;OR;COMPOSITE_TEST;1;TEST @Value(NATURE) = Ecomusée'0x11600'BOOL_OP;OR;COMPOSITE_TEST;1;TEST @Value(NATURE) = Elevage'0x02900'BOOL_OP;OR;COMPOSITE_TEST;1;TEST @Value(NATURE) = Enceinte militaire'0x0640b'BOOL_OP;OR;COMPOSITE_TEST;1;TEST @Value(NATURE) = Enseignement primaire'0x02c05'BOOL_OP;OR;COMPOSITE_TEST;1;TEST @Value(NATURE) = Enseignement supérieur'0x02c05'BOOL_OP;OR;COMPOSITE_TEST;1;TEST @Value(NATURE) = Espace public'0x1160d'BOOL_OP;OR;COMPOSITE_TEST;1;TEST @Value(NATURE) = Etablissement extraterritorial'0x03007'BOOL_OP;OR;COMPOSITE_TEST;1;TEST @Value(NATURE) = Etablissement hospitalier'0x03002'BOOL_OP;OR;COMPOSITE_TEST;1;TEST @Value(NATURE) = Etablissement pénitentiaire'0x02900'BOOL_OP;OR;COMPOSITE_TEST;1;TEST @Value(NATURE) = Etablissement thermal'0x02900'BOOL_OP;OR;COMPOSITE_TEST;1;TEST @Value(NATURE) = Gendarmerie'0x03001'BOOL_OP;OR;COMPOSITE_TEST;1;TEST @Value(NATURE) = Golf'0x02d05'BOOL_OP;OR;COMPOSITE_TEST;1;TEST @Value(NATURE) = Habitation troglodytique'0x11509'BOOL_OP;OR;COMPOSITE_TEST;1;TEST @Value(NATURE) = Haras'0x02d0a'BOOL_OP;OR;COMPOSITE_TEST;1;TEST @Value(NATURE) = Hébergement de loisirs'0x02b04'BOOL_OP;OR;COMPOSITE_TEST;1;TEST @Value(NATURE) = Hippodrome'0x02c08'BOOL_OP;OR;COMPOSITE_TEST;1;TEST @Value(NATURE) = Hôpital'0x03002'BOOL_OP;OR;COMPOSITE_TEST;1;TEST @Value(NATURE) = Hotel'0x02b01'BOOL_OP;OR;COMPOSITE_TEST;1;TEST @Value(NATURE) = Hôtel de département'0x03003'BOOL_OP;OR;COMPOSITE_TEST;1;TEST @Value(NATURE) = Lycée'0x02c05'BOOL_OP;OR;COMPOSITE_TEST;1;TEST @Value(NATURE) = Mairie'0x03003'BOOL_OP;OR;COMPOSITE_TEST;1;TEST @Value(NATURE) = Maison de retraite'0x02900'BOOL_OP;OR;COMPOSITE_TEST;1;TEST @Value(NATURE) = Maison du parc'0x06402'BOOL_OP;OR;COMPOSITE_TEST;1;TEST @Value(NATURE) = Maison forestière'0x14e01'BOOL_OP;OR;COMPOSITE_TEST;1;TEST @Value(NATURE) = Marais salant'0x02900'BOOL_OP;OR;COMPOSITE_TEST;1;TEST @Value(NATURE) = Marché'0x02e04'BOOL_OP;OR;COMPOSITE_TEST;1;TEST @Value(NATURE) = Mégalithe'0x11508'BOOL_OP;OR;COMPOSITE_TEST;1;TEST @Value(NATURE) = Mine'0x0640c'BOOL_OP;OR;COMPOSITE_TEST;1;TEST @Value(NATURE) = Monument'0x14e0f'BOOL_OP;OR;COMPOSITE_TEST;1;TEST @Value(NATURE) = Musée'0x02c02'BOOL_OP;OR;COMPOSITE_TEST;1;TEST @Value(NATURE) = Office de tourisme'0x02f0c'BOOL_OP;OR;COMPOSITE_TEST;1;TEST @Value(NATURE) = Ouvrage militaire'0x0640b'BOOL_OP;OR;COMPOSITE_TEST;1;TEST @Value(NATURE) = Palais de justice'0x03004'BOOL_OP;OR;COMPOSITE_TEST;1;TEST @Value(NATURE) = Parc de loisirs'0x02c01'BOOL_OP;OR;COMPOSITE_TEST;1;TEST @Value(NATURE) = Parc des expositions'0x10d09'BOOL_OP;OR;COMPOSITE_TEST;1;TEST @Value(NATURE) = Parc zoologique'0x02c07'BOOL_OP;OR;COMPOSITE_TEST;1;TEST @Value(NATURE) = Patinoire'0x02d08'BOOL_OP;OR;COMPOSITE_TEST;1;TEST @Value(NATURE) = Piscine'0x02d09'BOOL_OP;OR;COMPOSITE_TEST;1;TEST @Value(NATURE) = Point de vue'0x02c04'BOOL_OP;OR;COMPOSITE_TEST;1;TEST @Value(NATURE) = Police'0x03001'BOOL_OP;OR;COMPOSITE_TEST;1;TEST @Value(NATURE) = Poste'0x02f05'BOOL_OP;OR;COMPOSITE_TEST;1;TEST @Value(NATURE) = Préfecture'0x03007'BOOL_OP;OR;COMPOSITE_TEST;1;TEST @Value(NATURE) = Préfecture de région'0x03007'BOOL_OP;OR;COMPOSITE_TEST;1;TEST @Value(NATURE) = Refuge'0x02b04'BOOL_OP;OR;COMPOSITE_TEST;1;TEST @Value(NATURE) = Restaurant'0x02a0e'BOOL_OP;OR;COMPOSITE_TEST;1;TEST @Value(NATURE) = Salle de danse ou de jeux'0x02d04'BOOL_OP;OR;COMPOSITE_TEST;1;TEST @Value(NATURE) = Salle de spectacle ou conférence'0x02d01'BOOL_OP;OR;COMPOSITE_TEST;1;TEST @Value(NATURE) = Science'0x02c05'BOOL_OP;OR;COMPOSITE_TEST;1;TEST @Value(NATURE) = Sentier de découverte'0x06412'BOOL_OP;OR;COMPOSITE_TEST;1;TEST @Value(NATURE) = Siège d'EPCI'0x03003'BOOL_OP;OR;COMPOSITE_TEST;1;TEST @Value(NATURE) = Site d'escalade'0x11601'BOOL_OP;OR;COMPOSITE_TEST;1;TEST @Value(NATURE) = Site de vol libre'0x02d0b'BOOL_OP;OR;COMPOSITE_TEST;1;TEST @Value(NATURE) = Sous-préfecture'0x03007'BOOL_OP;OR;COMPOSITE_TEST;1;TEST @Value(NATURE) = Sports en eaux vives'0x11601'BOOL_OP;OR;COMPOSITE_TEST;1;TEST @Value(NATURE) = Sports mécaniques'0x11601'BOOL_OP;OR;COMPOSITE_TEST;1;TEST @Value(NATURE) = Sports nautiques'0x11601'BOOL_OP;OR;COMPOSITE_TEST;1;TEST @Value(NATURE) = Stade'0x02c08'BOOL_OP;OR;COMPOSITE_TEST;1;TEST @Value(NATURE) = Stand de tir'0x02900'BOOL_OP;OR;COMPOSITE_TEST;1;TEST @Value(NATURE) = Station de pompage'0x02900'BOOL_OP;OR;COMPOSITE_TEST;1;TEST @Value(NATURE) = Station d'épuration'0x02900'BOOL_OP;OR;COMPOSITE_TEST;1;TEST @Value(NATURE) = Structure d'accueil pour personnes handicapées'0x02900'BOOL_OP;OR;COMPOSITE_TEST;1;TEST @Value(NATURE) = Surveillance maritime'0x1151f'BOOL_OP;OR;COMPOSITE_TEST;1;TEST @Value(NATURE) = Tombeau'0x06403'BOOL_OP;OR;COMPOSITE_TEST;1;TEST @Value(NATURE) = Université'0x02c05'BOOL_OP;OR;COMPOSITE_TEST;1;TEST @Value(NATURE) = Usine'0x02900'BOOL_OP;OR;COMPOSITE_TEST;1;TEST @Value(NATURE) = Usine de production d'eau potable'0x02900'BOOL_OP;OR;COMPOSITE_TEST;1;TEST @Value(NATURE) = Vestige archéologique'0x1150b'BOOL_OP;OR;COMPOSITE_TEST;1;TEST @Value(NATURE) = Zone industrielle'0x02900'FME_NUM_CONDITIONS103___
      SET_TO EndLevel = 2
      SET_TO MPBITLEVEL = 22
      REMOVE NATURE
    -> StringCaseChanger-TOPONYMIE_SERVICES_ET_ACTIVITES
StringCaseChanger-TOPONYMIE_SERVICES_ET_ACTIVITES
    ATTRCHOICE = Selected Attributes
    ATTRLIST = NAME
    CHANGE_TYPE = Title case
    -> AttributeEncoder-TOPONYMIE_SERVICES_ET_ACTIVITES
AttributeEncoder-TOPONYMIE_SERVICES_ET_ACTIVITES
    ATTRCHOICE = All Attributes
    DEST_ENCODING = windows-1252
    TREAT_AS_BYTES = Honor Encoding
    -> Tester-TOPONYMIE_SERVICES_ET_ACTIVITES
Note: NON NULL
Tester-TOPONYMIE_SERVICES_ET_ACTIVITES
    BOOL_OP = OR
    TEST_CLAUSE = TEST MP_TYPE NOT_ATTRIBUTE_VALUE_NULL ""
    TEST_MODE = TEST
    PASSED -> FeatureWriter-TOPONYMIE_SERVICES_ET_ACTIVITES [Output03]
FeatureWriter-TOPONYMIE_SERVICES_ET_ACTIVITES
    COORDSYS = EPSG:4326
    DATASET = $(OUTPUT_DATA_TERRITORY)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = windows-1252
    SHAPEFILE_ENFORCE_ATTRIBUTE_LIMIT = No
    SHAPEFILE_MEASURES_AS_Z = No
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
ZONE_D_ACTIVITE_OU_D_INTERET (reader SHAPEFILE_19)
    attributes: ID varchar(24), CATEGORIE varchar(26), NATURE varchar(47), NAT_DETAIL varchar(62), TOPONYME varchar(127), STATUT_TOP varchar(10), IMPORTANCE varchar(1), FICTIF varchar(3), ETAT varchar(15), DATE_CREAT varchar(19), DATE_MAJ varchar(19), DATE_APP date, DATE_CONF date, SOURCE varchar(127), ID_SOURCE varchar(254), ACQU_PLANI varchar(32), PREC_PLANI float, ID_BAN varchar(12), NOMCOMMERC varchar(100)
    -> DuplicateFilter-ZONE_D_ACTIVITE_OU_D_INTERET
DuplicateFilter-ZONE_D_ACTIVITE_OU_D_INTERET
    INPUT_ORDERED_CHOICE = No
    KEYATTR = ID
    UNIQUE -> 2DForcer-ZONE_D_ACTIVITE_OU_D_INTERET
2DForcer-ZONE_D_ACTIVITE_OU_D_INTERET
    2D -> Reprojector-ZONE_D_ACTIVITE_OU_D_INTERET
Reprojector-ZONE_D_ACTIVITE_OU_D_INTERET
    DEST = EPSG:4326
    INTERPOLATION_TYPE_NAME = Nearest Neighbor
    RASTER_CELL_SIZE = Preserve Cells
    RASTER_TOLERANCE = 0.0
    SOURCE = EPSG:2154
    REPROJECTED -> Tester-ZoneIndustrielle
Tester-ZoneIndustrielle
    BOOL_OP = OR
    TEST_CLAUSE = TEST @Value(NATURE) = Zone industrielle
    TEST_MODE = TEST
    PASSED -> AttributeKeeper-ZONE_D_ACTIVITE_OU_D_INTERET
AttributeKeeper-ZONE_D_ACTIVITE_OU_D_INTERET
    CREATE_BULK_MODE_FEATURES = NO
    KEEP_ATTRS = TOPONYME
    -> AttributeManager-ZONE_D_ACTIVITE_OU_D_INTERET
AttributeManager-ZONE_D_ACTIVITE_OU_D_INTERET
    ATTR_TABLE:
      RENAME_SET_VALUE TOPONYME > NAME = FME_CONDITIONAL:DEFAULT_VALUE'@Value(NAME)'BOOL_OP;OR;COMPOSITE_TEST;1;TEST NAME ATTRIBUTE_IS_MISSING _FME_BLANK_STRING_'FME_NULL_VALUE'FME_NUM_CONDITIONS2___
      SET_TO MP_TYPE = 0x0c
      SET_TO EndLevel = 4
      SET_TO MPBITLEVEL = 20
    -> AttributeEncoder-ZONE_D_ACTIVITE_OU_D_INTERET
AttributeEncoder-ZONE_D_ACTIVITE_OU_D_INTERET
    ATTRCHOICE = All Attributes
    DEST_ENCODING = windows-1252
    TREAT_AS_BYTES = Honor Encoding
    -> StringCaseChanger-ZONE_D_ACTIVITE_OU_D_INTERET
StringCaseChanger-ZONE_D_ACTIVITE_OU_D_INTERET
    ATTRCHOICE = Selected Attributes
    ATTRLIST = NAME
    CHANGE_TYPE = Full Title Case
    -> Tester-ZONE_D_ACTIVITE_OU_D_INTERET
Note: NON NULL
Tester-ZONE_D_ACTIVITE_OU_D_INTERET
    BOOL_OP = OR
    TEST_CLAUSE = TEST MP_TYPE NOT_ATTRIBUTE_VALUE_NULL ""
    TEST_MODE = TEST
    PASSED -> FeatureWriter-ZONE_D_ACTIVITE_OU_D_INTERET [Output03]
FeatureWriter-ZONE_D_ACTIVITE_OU_D_INTERET
    COORDSYS = EPSG:4326
    DATASET = $(OUTPUT_DATA_TERRITORY)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = windows-1252
    SHAPEFILE_ENFORCE_ATTRIBUTE_LIMIT = No
    SHAPEFILE_MEASURES_AS_Z = No
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
LIGNE_ELECTRIQUE (reader SHAPEFILE_20)
    attributes: ID varchar(24), VOLTAGE varchar(12), ETAT varchar(15), DATE_CREAT varchar(19), DATE_MAJ varchar(19), DATE_APP date, DATE_CONF date, SOURCE varchar(127), ID_SOURCE varchar(254), ACQU_PLANI varchar(32), PREC_PLANI float, ACQU_ALTI varchar(30), PREC_ALTI float
    -> DuplicateFilter-LIGNE_ELECTRIQUE
DuplicateFilter-LIGNE_ELECTRIQUE
    INPUT_ORDERED_CHOICE = No
    KEYATTR = ID
    UNIQUE -> 2DForcer-LIGNE_ELECTRIQUE
2DForcer-LIGNE_ELECTRIQUE
    2D -> Reprojector-LIGNE_ELECTRIQUE
Reprojector-LIGNE_ELECTRIQUE
    DEST = EPSG:4326
    INTERPOLATION_TYPE_NAME = Nearest Neighbor
    RASTER_CELL_SIZE = Preserve Cells
    RASTER_TOLERANCE = 0.0
    SOURCE = EPSG:2154
    REPROJECTED -> AttributeKeeper-LIGNE_ELECTRIQUE
AttributeKeeper-LIGNE_ELECTRIQUE
    CREATE_BULK_MODE_FEATURES = NO
    KEEP_ATTRS = VOLTAGE
    -> AttributeManager-LIGNE_ELECTRIQUE
AttributeManager-LIGNE_ELECTRIQUE
    ATTR_TABLE:
      RENAME_SET_VALUE VOLTAGE > NAME = Ligne @Value(NAME)
      SET_TO MP_TYPE = 0x29
      SET_TO EndLevel = 2
      SET_TO MPBITLEVEL = 22
    -> AttributeEncoder-LIGNE_ELECTRIQUE
AttributeEncoder-LIGNE_ELECTRIQUE
    ATTRCHOICE = All Attributes
    DEST_ENCODING = windows-1252
    TREAT_AS_BYTES = Honor Encoding
    -> Tester-LIGNE_ELECTRIQUE
Note: NON NULL
Tester-LIGNE_ELECTRIQUE
    BOOL_OP = OR
    TEST_CLAUSE = TEST MP_TYPE NOT_ATTRIBUTE_VALUE_NULL ""
    TEST_MODE = TEST
    PASSED -> FeatureWriter-LIGNE_ELECTRIQUE [Output03]
FeatureWriter-LIGNE_ELECTRIQUE
    COORDSYS = EPSG:4326
    DATASET = $(OUTPUT_DATA_TERRITORY)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = windows-1252
    SHAPEFILE_ENFORCE_ATTRIBUTE_LIMIT = No
    SHAPEFILE_MEASURES_AS_Z = No
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written

Bookmark: ZONES REGLEMENTEES
FORET_PUBLIQUE (reader SHAPEFILE_21)
    attributes: ID varchar(24), NATURE varchar(21), TOPONYME varchar(127), STATUT_TOP varchar(10), IMPORTANCE varchar(1), DATE_CREAT varchar(19), DATE_MAJ varchar(19), DATE_APP date, DATE_CONF date, SOURCE varchar(127), ID_SOURCE varchar(254), ACQU_PLANI varchar(32), PREC_PLANI float
    -> DuplicateFilter-FORET_PUBLIQUE
DuplicateFilter-FORET_PUBLIQUE
    INPUT_ORDERED_CHOICE = No
    KEYATTR = ID
    UNIQUE -> 2DForcer-FORET_PUBLIQUE
2DForcer-FORET_PUBLIQUE
    2D -> Reprojector-FORET_PUBLIQUE
Reprojector-FORET_PUBLIQUE
    DEST = EPSG:4326
    INTERPOLATION_TYPE_NAME = Nearest Neighbor
    RASTER_CELL_SIZE = Preserve Cells
    RASTER_TOLERANCE = 0.0
    SOURCE = EPSG:2154
    REPROJECTED -> AttributeKeeper-FORET_PUBLIQUE
AttributeKeeper-FORET_PUBLIQUE
    CREATE_BULK_MODE_FEATURES = NO
    KEEP_ATTRS = TOPONYME
    -> AttributeManager-FORET_PUBLIQUE
AttributeManager-FORET_PUBLIQUE
    ATTR_TABLE:
      RENAME_SET_VALUE TOPONYME > NAME = FME_CONDITIONAL:DEFAULT_VALUE'@Value(NAME)'BOOL_OP;OR;COMPOSITE_TEST;1;TEST NAME ATTRIBUTE_IS_MISSING _FME_BLANK_STRING_'FME_NULL_VALUE'FME_NUM_CONDITIONS2___
      SET_TO MP_TYPE = 0x10a03
      SET_TO EndLevel = 3
      SET_TO MPBITLEVEL = 21
    -> AttributeEncoder-FORET_PUBLIQUE
AttributeEncoder-FORET_PUBLIQUE
    ATTRCHOICE = All Attributes
    DEST_ENCODING = windows-1252
    TREAT_AS_BYTES = Honor Encoding
    -> Tester-FORET_PUBLIQUE
Note: NON NULL
Tester-FORET_PUBLIQUE
    BOOL_OP = OR
    TEST_CLAUSE = TEST MP_TYPE NOT_ATTRIBUTE_VALUE_NULL ""
    TEST_MODE = TEST
    PASSED -> FeatureWriter-FORET_PUBLIQUE [Output03]
FeatureWriter-FORET_PUBLIQUE
    COORDSYS = EPSG:4326
    DATASET = $(OUTPUT_DATA_TERRITORY)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = windows-1252
    SHAPEFILE_ENFORCE_ATTRIBUTE_LIMIT = No
    SHAPEFILE_MEASURES_AS_Z = No
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
